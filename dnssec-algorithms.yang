module dnssec-algorithms {

  yang-version "1.1";

  namespace "http://www.nic.cz/ns/yang/dnssec-algorithms";

  prefix "dsalg";

  organization
    "CZ.NIC, z. s. p. o.";

  contact
    "Editor:   Ladislav Lhotka
               <mailto:lhotka@nic.cz>";

  description
    "This module translates IANA registry for DNSSEC algorithm
     numbers to a YANG enumeration type.";

  reference
    "IANA: Domain Name System Security (DNSSEC) Algorithm Numbers.
     http://www.iana.org/assignments/dns-sec-alg-numbers/dns-sec-alg-numbers.xhtml";

  revision 2015-06-19 {
    description
      "Initial revision.";
  }

  typedef dnssec-algorithm {
    type enumeration {
      enum RSAMD5 {
        value "1";
        status "deprecated";
        description
          "RSA/MD5";
      }
      enum DH {
        value "2";
        description
          "Diffie-Hellman";
      }
      enum DSA {
        value "3";
        description
          "DSA/SHA1";
      }
      enum RSASHA1 {
        value "5";
        description
          "RSA/SHA1";
      }
      enum DSA-NSEC3-SHA1 {
        value "6";
        description
          "DSA-NSEC3-SHA1";
      }
      enum RSASHA1-NSEC3-SHA1 {
        value "7";
        description
          "RSASHA1-NSEC3-SHA1";
      }
      enum RSASHA256 {
        value "8";
        description
          "RSA/SHA256";
      }
      enum RSASHA512 {
        value "10";
        description
          "RSA/SHA512";
      }
      enum ECC-GOST {
        value "12";
        description
          "GOST R 34.10-2001";
      }
      enum ECDSAP256SHA256 {
        value "13";
        description
          "ECDSA Curve P-256 with SHA-256";
      }
      enum ECDSAP384SHA384 {
        value "14";
        description
          "ECDSA Curve P-384 with SHA-384";
      }
    }
    description
      "This typedef defines an enumeration of algorithms for DNSSEC
       signing as defined by IANA.

       The numbers defined by the 'value' statements are used in KEY,
       SIG, DNSKEY, RRSIG and CERT resource records for identifying
       the security algorithm.

       Value 0, 4, 9 and 11 are reserved.";
  }
}
